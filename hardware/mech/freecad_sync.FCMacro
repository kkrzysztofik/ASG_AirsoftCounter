"""Edit the insert's dimensions in FreeCAD, with params.py staying the source of truth.

Run it once (Macro > Macros..., or a toolbar button): it opens out/assembly.step and adds a
Params sheet with every plain number in params.py. Edit values in the sheet, run it again: the
changed numbers go into params.py, the parts are rebuilt and checked, and the assembly reloads.
A failed check puts params.py back as it was and keeps your edits in the sheet.
FreeCAD freezes while it rebuilds (a minute or so); choose Wait. If it was killed mid-sync:
`git checkout mech/params.py && make mech`.

Only scalars are editable; tuples, lists and derived values stay in params.py. Needs uv on the
PATH FreeCAD sees. Test the non-GUI half on a plain Python:

    /usr/bin/python3 hardware/mech/freecad_sync.FCMacro --selftest
"""

import ast
import hashlib
import io
import os
import pathlib
import shutil
import subprocess
import sys

HERE = pathlib.Path(__file__).resolve().parent
PARAMS = HERE / "params.py"
ASSEMBLY = HERE / "out" / "assembly.step"
SHEET = "Params"
MEASURE_RGB = (1.0, 0.95, 0.6)


# --- params.py, no FreeCAD ------------------------------------------------------------------------


def _number(node):
    if isinstance(node, ast.Constant) and type(node.value) in (int, float):
        return node.value
    if isinstance(node, ast.UnaryOp) and isinstance(node.op, ast.USub):
        inner = _number(node.operand)
        return None if inner is None else -inner
    return None


def leaves(text):
    """[(name, value, line, col, end_col, comment)] for every top-level `NAME = <number>`.

    line is 1-based, col and end_col are UTF-8 byte offsets of the value, as ast gives them.
    """
    lines = io.StringIO(text, newline="").readlines()  # split where ast does: \n, \r\n, \r only
    out = []
    for node in ast.parse(text).body:
        if not (isinstance(node, ast.Assign) and len(node.targets) == 1
                and isinstance(node.targets[0], ast.Name)):
            continue
        value = _number(node.value)
        if value is None or node.value.lineno != node.value.end_lineno:
            continue
        raw = lines[node.value.lineno - 1].encode()
        rest = raw[node.value.end_col_offset:].decode()
        comment = rest.split("#", 1)[1].strip() if "#" in rest else ""
        out.append((node.targets[0].id, value, node.value.lineno,
                    node.value.col_offset, node.value.end_col_offset, comment))
    return out


def rewrite(text, changes):
    """text with each changed value's span replaced; every other byte untouched."""
    lines = io.StringIO(text, newline="").readlines()
    # right to left, so an edit never shifts the offsets of one still to come on the same line
    for name, value, line, col, end, _c in sorted(leaves(text), key=lambda leaf: (leaf[2], leaf[3]), reverse=True):
        if name not in changes:
            continue
        new = changes[name]
        lit = str(int(new)) if isinstance(value, int) and float(new).is_integer() else repr(float(new))
        raw = lines[line - 1].encode()
        lines[line - 1] = (raw[:col] + lit.encode() + raw[end:]).decode()
    return "".join(lines)


def digest(text):
    return hashlib.sha256(text.encode()).hexdigest()


def selftest():
    text = PARAMS.read_bytes().decode()
    found = {leaf[0]: leaf for leaf in leaves(text)}
    assert {"WALL", "LID_T", "BUTTON_D"} <= set(found), sorted(found)
    assert "BOX_IN" not in found and "FIT" not in found, "tuples and derived values are not leaves"
    changes = {"WALL": 3.25, "LID_T": 2.0, "BUTTON_D": 19.0}
    new = rewrite(text, changes)
    old_lines, new_lines = text.splitlines(), new.splitlines()
    assert len(old_lines) == len(new_lines)
    diff = [(a, b) for a, b in zip(old_lines, new_lines) if a != b]
    assert len(diff) == 3, diff
    for a, b in diff:
        assert a.split("#", 1)[1:] == b.split("#", 1)[1:], (a, b)  # comment survives byte for byte
    after = {leaf[0]: leaf[1] for leaf in leaves(new)}
    assert all(after[k] == v for k, v in changes.items()), after
    assert rewrite(text, {}) == text
    assert rewrite("N = 4  # int\n", {"N": 5.0}) == "N = 5  # int\n"
    assert rewrite("N = -1.5\n", {"N": -2.0}) == "N = -2.0\n"
    assert rewrite("A = 1; B = 22\n", {"A": 1000, "B": 3}) == "A = 1000; B = 3\n"
    assert rewrite("# a\x0cb\nX = 1\n", {"X": 5}) == "# a\x0cb\nX = 5\n"
    assert rewrite(new, {k: found[k][1] for k in changes}) == text  # round trip
    print(f"ok    selftest: {len(found)} leaves, 3 edits touch exactly 3 lines, comments intact")
    return 0


# --- FreeCAD ----------------------------------------------------------------------------------------


def _uv():
    for c in (shutil.which("uv"), os.path.expanduser("~/.local/bin/uv"), os.path.expanduser("~/.cargo/bin/uv")):
        if c and os.path.exists(c):
            return c
    raise RuntimeError("uv not found. FreeCAD's PATH is:\n" + os.environ.get("PATH", ""))


def _run_checks():
    """(ok, output, index of the failed step or None) for the full rebuild. check.py goes first:
    it is instant and writes nothing, while insert.py rewrites out/ part by part."""
    uv = _uv()
    steps = [
        [uv, "run", "check.py"],
        [uv, "run", "insert.py", "--part", "all", "--check"],
        [uv, "run", "insert.py", "--part", "assembly", "--check"],
    ]
    # the FreeCAD AppImage exports these, and they break uv's Python
    env = {k: v for k, v in os.environ.items() if k not in ("PYTHONHOME", "PYTHONPATH", "LD_LIBRARY_PATH")}
    log = []
    for i, cmd in enumerate(steps):
        r = subprocess.run(cmd, cwd=HERE, capture_output=True, encoding="utf-8", errors="replace", env=env)
        log.append(f"$ {' '.join(cmd[1:])}\n{r.stdout}{r.stderr}")
        if r.returncode:
            return False, "\n".join(log), i
    return True, "\n".join(log), None


def load():
    import FreeCAD as App

    if App.GuiUp:
        import ImportGui as Import  # keeps the STEP colours
    else:
        import Import

    if not ASSEMBLY.exists():
        raise RuntimeError(f"{ASSEMBLY} is missing: run `uv run insert.py --part assembly` first")
    Import.open(str(ASSEMBLY))
    doc = App.ActiveDocument
    text = PARAMS.read_bytes().decode()
    sheet = doc.addObject("Spreadsheet::Sheet", SHEET)
    sheet.addProperty("App::PropertyString", "ParamsHash")
    sheet.set("A1", "name")
    sheet.set("B1", "value")
    sheet.set("C1", "params.py comment")
    for row, (name, value, _l, _c, _e, comment) in enumerate(leaves(text), start=2):
        sheet.set(f"A{row}", name)
        sheet.set(f"B{row}", repr(value))
        sheet.setAlias(f"B{row}", name)
        sheet.set(f"C{row}", "'" + comment)
        if "MEASURE" in comment:
            sheet.setBackground(f"A{row}:C{row}", MEASURE_RGB)
    sheet.ParamsHash = digest(text)  # last: a half-built sheet never matches params.py
    doc.recompute()
    return doc


def sync(doc):
    import FreeCAD as App

    doc.recompute()  # a cell edit may not be recalculated yet
    sheet = doc.getObject(SHEET)
    text = PARAMS.read_bytes().decode()
    if digest(text) != sheet.ParamsHash:
        return _say("params.py changed on disk since this sheet was loaded. Close this document "
                    "and run the macro again to reload; nothing was written.")
    changes = {}
    for name, value, *_ in leaves(text):
        v = sheet.get(name)
        try:
            v = float(getattr(v, "Value", v))
        except (TypeError, ValueError):
            return _say(f"{name}: {v!r} is not a number; nothing was written.")
        if v != value:
            changes[name] = v
    if not changes:
        return _say("No parameter changed.")
    try:
        PARAMS.write_bytes(rewrite(text, changes).encode())
        ok, log, failed = _run_checks()
    except Exception as exc:  # uv missing, a failed write, anything: never leave params.py half-applied
        ok, log, failed = False, str(exc), 0  # nothing got as far as insert.py
    if not ok:
        PARAMS.write_bytes(text.encode())
        if failed == 0:  # check.py writes nothing
            note = "out/ untouched"
        else:
            # insert.py failed midway: out/ is half rebuilt with the rejected values; rebuild it
            try:
                rebuilt = _run_checks()[0]
            except Exception:
                rebuilt = False
            note = "out/ rebuilt from it" if rebuilt else "REBUILD OF out/ FAILED, run `make mech`"
        return _say(f"A check failed; params.py is restored, {note}, your edits stay in the sheet.\n\n"
                    + log[-3000:])
    App.closeDocument(doc.Name)
    load()
    _say("Updated " + ", ".join(f"{k} = {v!r}" for k, v in changes.items()))


def _say(msg):
    import FreeCAD as App

    App.Console.PrintMessage(msg + "\n")
    if App.GuiUp:  # headless (freecadcmd) has no QApplication; a dialog there aborts FreeCAD
        from PySide import QtGui
        QtGui.QMessageBox.information(None, "freecad_sync", msg)


def main():
    import FreeCAD as App

    doc = App.ActiveDocument
    if doc is not None and doc.getObject(SHEET) is not None:
        sync(doc)
    else:
        load()


if "--selftest" in sys.argv:
    sys.exit(selftest())
else:
    main()
